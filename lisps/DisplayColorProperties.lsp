;;; DisplayColorProperties.LSP
;;; Miscellaneous commands related to Colors on the Display tab on the Options dialog
;;; By Jimmy Bergmark
;;; Copyright (C) 1997-2006 JTB World, All Rights Reserved
;;; Website: www.jtbworld.com
;;; E-mail: info@jtbworld.com
;;; 2000-03-29 - First release
;;; 2003-03-07 - Now for AutoCAD 2004
;;; 2003-05-14 - Added ACI to RGB conversion
;;; Tested on AutoCAD 2000, 2000i, 2002 and 2004
;;; Some bugs exist with the conversions of colors from RGB to ACI.

(vl-load-com)

(setq pref (vla-get-preferences (vlax-get-acad-object)))

(setq display (vla-get-display pref))

;;; Set the ModelColor using the color dialog box
(defun c:SetModelColor(/ col oldcol)
  (setq oldcol (getGraphicsWinModelBackgrndColor))
  (if (= oldcol nil) (setq oldcol 0))
  (if (= oldcol 0) (setq oldcol 1))
  (setq col (acad_colordlg oldcol nil))
  (if (and (= oldcol 7) (= col 7)) (setq col 0))
  (if (/= col nil) (putGraphicsWinModelBackgrndColor col))
  (princ)
)
(defun c:SetModelColor2004(/ col oldcol)
  (setq oldcol (getGraphicsWinModelBackgrndColor2004))
  (if (= oldcol nil) (setq oldcol 0))
  (if (= oldcol 0) (setq oldcol 1))
  (setq col (acad_colordlg oldcol nil))
  (if (and (= oldcol 7) (= col 7)) (setq col 0))
  (if (/= col nil) (putGraphicsWinModelBackgrndColor col))
  (princ)
)

;;; Set the LayoutColor using the color dialog box
(defun c:SetLayoutColor(/ col oldcol)
  (setq oldcol (getGraphicsWinLayoutBackgrndColor))
  (if (= oldcol nil) (setq oldcol 0))
  (if (= oldcol 0) (setq oldcol 1))
  (setq col (acad_colordlg oldcol nil))
  (if (and (= oldcol 7) (= col 7)) (setq col 0))
  (if (/= col nil) (putGraphicsWinLayoutBackgrndColor col))
  (princ)
)

(defun getGraphicsWinModelBackgrndColor()
  (OLE_color->ACI_color 
    (vla-get-GraphicsWinModelBackgrndColor
      (vla-get-display (vla-get-preferences (vlax-get-acad-object)))))
)

(defun getGraphicsWinModelBackgrndColor2004 ()
  (OLE_colorToACI
    (vlax-variant-value
      (vlax-variant-change-type
	(vla-get-GraphicsWinModelBackgrndColor
	  (vla-get-display
	    (vla-get-preferences (vlax-get-acad-object))
	  )
	)
	vlax-vbLong
      )
    )
  )
)

(defun putGraphicsWinModelBackgrndColor(col)
  (vla-put-GraphicsWinModelBackgrndColor
    (vla-get-display (vla-get-preferences (vlax-get-acad-object)))
    (ACI_color->OLE_color col)
  )
)

(defun getGraphicsWinLayoutBackgrndColor()
  (OLE_color->ACI_color 
    (vla-get-GraphicsWinLayoutBackgrndColor
      (vla-get-display (vla-get-preferences (vlax-get-acad-object)))))
)

(defun putGraphicsWinLayoutBackgrndColor(col)
  (vla-put-GraphicsWinLayoutBackgrndColor
    (vla-get-display (vla-get-preferences (vlax-get-acad-object)))
    (ACI_color->OLE_color col)
  )
)

(defun getModelCrosshairColor()
  (OLE_color->ACI_color 
    (vla-get-ModelCrosshairColor
      (vla-get-display (vla-get-preferences (vlax-get-acad-object)))))
)

(defun putModelCrosshairColor(col)
  (vla-put-ModelCrosshairColor
    (vla-get-display (vla-get-preferences (vlax-get-acad-object)))
    (ACI_color->OLE_color col)
  )
)

(defun getLayoutCrosshairColor()
  (OLE_color->ACI_color 
    (vla-get-LayoutCrosshairColor
      (vla-get-display (vla-get-preferences (vlax-get-acad-object)))))
)

(defun putLayoutCrosshairColor(col)
  (vla-put-LayoutCrosshairColor
    (vla-get-display (vla-get-preferences (vlax-get-acad-object)))
    (ACI_color->OLE_color col)
  )
)

(defun getTextWinBackgrndColor()
  (OLE_color->ACI_color 
    (vla-get-TextWinBackgrndColor
      (vla-get-display (vla-get-preferences (vlax-get-acad-object)))))
)

(defun putTextWinBackgrndColor(col)
  (vla-put-TextWinBackgrndColor
    (vla-get-display (vla-get-preferences (vlax-get-acad-object)))
    (ACI_color->OLE_color col)
  )
)

(defun getTextWinTextColor()
  (OLE_color->ACI_color 
    (vla-get-TextWinTextColor
      (vla-get-display (vla-get-preferences (vlax-get-acad-object)))))
)

(defun putTextWinTextColor(col)
  (vla-put-TextWinTextColor
    (vla-get-display (vla-get-preferences (vlax-get-acad-object)))
    (ACI_color->OLE_color col)
  )
)

(defun getAutoTrackingVecColor()
  (OLE_color->ACI_color 
    (vla-get-AutoTrackingVecColor
      display))
)

(defun putAutoTrackingVecColor(col)
  (vla-put-AutoTrackingVecColor
    display
    (ACI_color->OLE_color col)
  )
)

(defun OLE_color->ACI_color (olec)
  (vl-position
    (boole 1
           (vlax-variant-value
             (vlax-variant-change-type olec vlax-vbLong)
           )
           16777215
    )
    OLE_COLOR_LIST
  )
)


(defun ACI_color->OLE_color (aci)
  ; black is 0
  ; white is 7
  (if (and (>= aci 0) (= aci 0) (<= 255))
    (nth aci RGB_list)
  )
)

(setq RGB_list '(
		 (0 0 0)
		 (255 0 0)
		 (255 255 0)
		 (0 255 0)
		 (0 255 255)
		 (0 0 255)
		 (255 0 255)
		 (255 255 255)
		 (128 128 128)
		 (192 192 192)
		 (255 0 0)
		 (255 127 127)
		 (165 0 0)
		 (165 82 82)
		 (127 0 0)
		 (127 63 63)
		 (76 0 0)
		 (76 38 38)
		 (38 0 0)
		 (38 19 19)
		 (255 63 0)
		 (255 159 127)
		 (165 41 0)
		 (165 103 82)
		 (127 31 0)
		 (127 79 63)
		 (76 19 0)
		 (76 47 38)
		 (38 9 0)
		 (38 23 19)
		 (255 127 0)
		 (255 191 127)
		 (165 82 0)
		 (165 124 82)
		 (127 63 0)
		 (127 95 63)
		 (76 38 0)
		 (76 57 38)
		 (38 19 0)
		 (38 28 19)
		 (255 191 0)
		 (255 223 127)
		 (165 124 0)
		 (165 145 82)
		 (127 95 0)
		 (127 111 63)
		 (76 57 0)
		 (76 66 38)
		 (38 28 0)
		 (38 33 19)
		 (255 255 0)
		 (255 255 127)
		 (165 165 0)
		 (165 165 82)
		 (127 127 0)
		 (127 127 63)
		 (76 76 0)
		 (76 76 38)
		 (38 38 0)
		 (38 38 19)
		 (191 255 0)
		 (223 255 127)
		 (124 165 0)
		 (145 165 82)
		 (95 127 0)
		 (111 127 63)
		 (57 76 0)
		 (66 76 38)
		 (28 38 0)
		 (33 38 19)
		 (127 255 0)
		 (191 255 127)
		 (82 165 0)
		 (124 165 82)
		 (63 127 0)
		 (95 127 63)
		 (38 76 0)
		 (57 76 38)
		 (19 38 0)
		 (28 38 19)
		 (63 255 0)
		 (159 255 127)
		 (41 165 0)
		 (103 165 82)
		 (31 127 0)
		 (79 127 63)
		 (19 76 0)
		 (47 76 38)
		 (9 38 0)
		 (23 38 19)
		 (0 255 0)
		 (127 255 127)
		 (0 165 0)
		 (82 165 82)
		 (0 127 0)
		 (63 127 63)
		 (0 76 0)
		 (38 76 38)
		 (0 38 0)
		 (19 38 19)
		 (0 255 63)
		 (127 255 159)
		 (0 165 41)
		 (82 165 103)
		 (0 127 31)
		 (63 127 79)
		 (0 76 19)
		 (38 76 47)
		 (0 38 9)
		 (19 38 23)
		 (0 255 127)
		 (127 255 191)
		 (0 165 82)
		 (82 165 124)
		 (0 127 63)
		 (63 127 95)
		 (0 76 38)
		 (38 76 57)
		 (0 38 19)
		 (19 38 28)
		 (0 255 191)
		 (127 255 223)
		 (0 165 124)
		 (82 165 145)
		 (0 127 95)
		 (63 127 111)
		 (0 76 57)
		 (38 76 66)
		 (0 38 28)
		 (19 38 33)
		 (0 255 255)
		 (127 255 255)
		 (0 165 165)
		 (82 165 165)
		 (0 127 127)
		 (63 127 127)
		 (0 76 76)
		 (38 76 76)
		 (0 38 38)
		 (19 38 38)
		 (0 191 255)
		 (127 223 255)
		 (0 124 165)
		 (82 145 165)
		 (0 95 127)
		 (63 111 127)
		 (0 57 76)
		 (38 66 76)
		 (0 28 38)
		 (19 33 38)
		 (0 127 255)
		 (127 191 255)
		 (0 82 165)
		 (82 124 165)
		 (0 63 127)
		 (63 95 127)
		 (0 38 76)
		 (38 57 76)
		 (0 19 38)
		 (19 28 38)
		 (0 63 255)
		 (127 159 255)
		 (0 41 165)
		 (82 103 165)
		 (0 31 127)
		 (63 79 127)
		 (0 19 76)
		 (38 47 76)
		 (0 9 38)
		 (19 23 38)
		 (0 0 255)
		 (127 127 255)
		 (0 0 165)
		 (82 82 165)
		 (0 0 127)
		 (63 63 127)
		 (0 0 76)
		 (38 38 76)
		 (0 0 38)
		 (19 19 38)
		 (63 0 255)
		 (159 127 255)
		 (41 0 165)
		 (103 82 165)
		 (31 0 127)
		 (79 63 127)
		 (19 0 76)
		 (47 38 76)
		 (9 0 38)
		 (23 19 38)
		 (127 0 255)
		 (191 127 255)
		 (82 0 165)
		 (124 82 165)
		 (63 0 127)
		 (95 63 127)
		 (38 0 76)
		 (57 38 76)
		 (19 0 38)
		 (28 19 38)
		 (191 0 255)
		 (223 127 255)
		 (124 0 165)
		 (145 82 165)
		 (95 0 127)
		 (111 63 127)
		 (57 0 76)
		 (66 38 76)
		 (28 0 38)
		 (33 19 38)
		 (255 0 255)
		 (255 127 255)
		 (165 0 165)
		 (165 82 165)
		 (127 0 127)
		 (127 63 127)
		 (76 0 76)
		 (76 38 76)
		 (38 0 38)
		 (38 19 38)
		 (255 0 191)
		 (255 127 223)
		 (165 0 124)
		 (165 82 145)
		 (127 0 95)
		 (127 63 111)
		 (76 0 57)
		 (76 38 66)
		 (38 0 28)
		 (38 19 33)
		 (255 0 127)
		 (255 127 191)
		 (165 0 82)
		 (165 82 124)
		 (127 0 63)
		 (127 63 95)
		 (76 0 38)
		 (76 38 57)
		 (38 0 19)
		 (38 19 28)
		 (255 0 63)
		 (255 127 159)
		 (165 0 41)
		 (165 82 103)
		 (127 0 31)
		 (127 63 79)
		 (76 0 19)
		 (76 38 47)
		 (38 0 9)
		 (38 19 23)
		 (0 0 0)
		 (51 51 51)
		 (102 102 102)
		 (153 153 153)
		 (204 204 204)
		 (255 255 255)
		)
)

;;; Examples
;;; 
;;; (RGBtoACI '(91 91 91)) returns 251
;;; (RGBtoACI '(118 118 118)) returns 8
;;; (RGBtoOLE_color '(118 118 118)) gives OLE_color=7763574
;;; (OLEtoRGB_color 7763574) gives (118 118 118)
;;; (RGBtoOLE_color '(91 91 91)) gives OLE_color=5987163
;;; (OLEtoRGB_color 5987163) gives (91 91 91)
;;; (RGBtoACI '(101 101 101)) returns 8
;;; (OLEtoRGB_color 6645093) returns (101 101 101)
;;; (ACItoRGB 123)

;;; Missing is conversion from ACI to RGB or ACI to OLE_color
